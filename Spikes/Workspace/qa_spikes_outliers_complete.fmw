FME workspace qa_spikes_outliers_complete.fmw
Title: qa_spike_outliers
Description: Exemplo de remoção de Spikes & Outliers de dados geográficos com FME
History: 22/10/2024,thiago.brigagao,Criação de Workspace Template

Parameters:
- SourceDataset_IGDS = C:\Users\thiago.brigagao\Desktop\ST\2024\10\29\Dataset\Spikes\bathymetry.dgn   # Source Bentley MicroStation Design File(s)

Readers:
- IGDS_1: IGDS from $(SourceDataset_IGDS)

StatisticsCalculator_Complete: Inspector

Bookmark: 1.0 | Reader DGN
Note: Leitor | DGN | Dados de Batimetria
1 (reader IGDS_1)
    -> SpikeRemover

Bookmark: 2.1 | Reader DGN
Note: SpikeRemover [SpikeRemover Version 3] / General: / Maximum Spike Angle: 45 / Maximum Spike Length: 250 / Dimension: 2D / Remove Spikes Iteratively: No
SpikeRemover
    DIMENSIONS = 2D
    ITERATIVE = No
    SPIKEANGLE = 45
    SPIKELENGTH = 250
    REMOVED -> StatisticsCalculator

Bookmark: 2.2 | Reader DGN
Note: Contagem de quantos registros removemos
StatisticsCalculator
    ATTR_ACCUM_MODE = None
    CALCULATION_MODE = NUMERIC
    FEAT_STATS = _spike_angle,NUMERIC_MODE,,,COUNT,,,,,,,,,,
    COMPLETE -> StatisticsCalculator_Complete
